-- Especificação do arquivo de assinaturas da urna (vota.vsc) publicada pelo TSE na documentação
-- técnica do software da urna, versão de 2024 (cópia pública em github.com/doccaz/urnas-br,
-- docv2/spec/assinatura.asn1; a de 2022 está em github.com/lucasvmx/evmfd, asn/assinatura.asn1).
-- Dois ajustes para os arquivos de 2026, inferidos dos bytes e conferidos em todas as seções do
-- AC nos dois turnos e numa amostra de 9.900 seções do 2º turno em todas as UFs:
--   * EntidadeAssinaturaEcourna perdeu modeloEquipamento do início; o modelo vem no fim, numa
--     SEQUENCE com um segundo ENUMERATED que repete o algoritmo da assinatura de hardware
--     (2 = ecdsa nas UE2013 e UE2015, 4 = eddsa nas UE2020 e UE2022, sem exceção na amostra);
--   * conjuntoChave e certificadoDigital passaram a ter etiquetas de contexto [0] e [1].
-- O resto confere com a versão de 2024: SHA-512, CEPESC no software, Ed521 (eddsa, 521 bits)
-- nas UE2020/UE2022 e ECDSA P-521 nas anteriores, certificado em PEM (UE2020+) ou DER.
ModuloAssinaturaResultado DEFINITIONS IMPLICIT TAGS ::= BEGIN

EXPORTS ALL;

-- TIPOS
DataHoraJE ::= GeneralString(SIZE(15))  -- Data e hora utilizada pela Justiça Eleitoral no formato YYYYMMDDThhmmss.

-- ENUMS
-- Tipos de algoritmos de assinatura.
AlgoritmoAssinatura ::= ENUMERATED {
    rsa     (1),
    ecdsa   (2),
    cepesc  (3),
    eddsa   (4) -- Assinatura e521 para modelos UE2020 e posteriores
}

-- Tipos de algoritmos de hash (todos os algoritmos devem ser suportados, mas sha512 é o padrão).
AlgoritmoHash ::= ENUMERATED {
    sha1    (1),
    sha256  (2),
    sha384  (3),
    sha512  (4)
}

-- ENVELOPE
-- Entidade que engloba a lista de assinaturas utilizadas para assinar os arquivos.
EntidadeAssinatura ::= SEQUENCE {
    dataHoraCriacao         DataHoraJE,                                 -- Data e Hora da criacao do arquivo.
    versao                  INTEGER (2..99999999),                      -- Versao do protocolo.
    autoAssinado            AutoAssinaturaDigital,                      -- Informações da auto assinatura digital.
    conteudoAutoAssinado    OCTET STRING,                               -- Conteúdo (Assinatura codificada) da assinatura do próprio arquivo.
    conjuntoChave           [0] GeneralString(SIZE(1..15)) OPTIONAL,    -- 2026: etiqueta [0]; identificador do conjunto de chaves (vem na assinatura SW).
    certificadoDigital      [1] OCTET STRING OPTIONAL                   -- 2026: etiqueta [1]; certificado X.509 da urna, PEM ou DER (vem na assinatura HW).
}

-- 2026: fecho do arquivo com o modelo da urna. O nome do segundo campo é inferido: o valor
-- sempre coincide com o algoritmo da assinatura de hardware.
DescritorEquipamento ::= SEQUENCE {
    modeloEquipamento   ModeloEquipamento,
    algoritmoHardware   AlgoritmoAssinatura
}

-- Tipos de equipamentos que geram assinatura de hardware (versão de 2024).
ModeloEquipamento ::= ENUMERATED {
    tpm12   (1),
    tpm20   (2),
    ue2009  (9),
    ue2010  (10),
    ue2011  (11),
    ue2013  (13),
    ue2015  (15),
    ue2020  (20),
    ue2022  (22)
}

-- Arquivo vota.vsc de 2026: assinatura de software (CEPESC), assinatura de hardware (Ed521 ou ECDSA) e o
-- descritor do equipamento.
EntidadeAssinaturaEcourna2026 ::= SEQUENCE {
    assinaturaSW            EntidadeAssinatura,     -- Assinatura realizada via software (CEPESC).
    assinaturaHW            EntidadeAssinatura,     -- Assinatura realizada via hardware da urna (Ed521 ou ECDSA P-521).
    equipamento             DescritorEquipamento
}

-- Informações do algoritmo de assinatura.
AlgoritmoAssinaturaInfo ::= SEQUENCE {
    algoritmo   AlgoritmoAssinatura,    -- Tipo do algoritmo de assinatura.
    bits        INTEGER                 -- Tamanho da assinatura.
}

-- Informações do algoritmo de hash.
AlgoritmoHashInfo ::= SEQUENCE {
    algoritmo AlgoritmoHash -- Tipo do algoritmo de hash.
}

-- Informações dos arquivos assinados.
Assinatura ::= SEQUENCE {
    arquivosAssinados SEQUENCE OF AssinaturaArquivo -- Lista com Informações dos arquivos assinados.
}

-- Informações do arquivo e da assinatura.
AssinaturaArquivo ::= SEQUENCE {
    nomeArquivo GeneralString,      -- Nome do arquivo.
    assinatura  AssinaturaDigital   -- Assinatura digital do arquivo.
}

-- Informações da assinatura digital.
AssinaturaDigital ::= SEQUENCE {
    tamanho     INTEGER,        -- Tamanho do arquivo assinado, em bytes.
    hash        OCTET STRING,   -- SHA-512 do arquivo.
    assinatura  OCTET STRING    -- Assinatura (gerada/verificada a partir do hash acima).
}

-- Informações da auto assinatura digital.
AutoAssinaturaDigital ::= SEQUENCE {
    usuario             DescritorChave,             -- Nome do usuário que realizou a assinatura do arquivo.
    algoritmoHash       AlgoritmoHashInfo,          -- Algoritmo de hash utilizado para realizar a assinatura.
    algoritmoAssinatura AlgoritmoAssinaturaInfo,    -- Algoritmo utilizado para realizar a assinatura.
    assinatura          AssinaturaDigital           -- Informações da assinatura digital.
}

-- Identificador com informações da assinatura.
DescritorChave ::= SEQUENCE {
    nomeUsuario GeneralString,  -- Nome do usuário que realizou a assinatura no arquivo.
    serial      INTEGER         -- Data em que foi gerado o conjunto de chaves.
}

END
